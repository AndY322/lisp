(defun getpt ()
  (setq pt (getpoint "\n Укажите точку \n"))
  (setq specify_x (rtos (car pt) 2 3))
  (setq specify_y (rtos (cadr pt) 2 3))
)

(defun getcolor	()
  (setq num_color (atoi (getvar "cecolor")))
  (setq num_color (acad_colordlg num_color))
  (command "color" num_color)
)

(defun draw()
	(setq p (strcat specify_x "," specify_y))
	(setq cr (cons p cr))
	(if (= close1 "1") (setq varclose "close") (setq varclose ""))
	(if (= sm "1") (setq sm "spline") (setq sm ""))
	(command "lweight" line_width)
	(command "pline")
	(foreach a cr
		(command a)
	)
	(command varclose)
	(setq lastvar (entlast))
	(command "pedit" lastvar sm "")
	(setq w_n 0)
)

(defun test()
	(command "pline")
	(foreach a cr
		(command a)
	)
)

(defun readfile()

  (setq coordinates (open "d:\\LISP\\coordinates.txt" "r"))
  (setq coordinate (list))
	(setq i (read-line coordinates))
	(setq i (atoi i))
  (repeat i
	(setq rf (read-line coordinates))
	(setq coordinate (cons rf coordinate))
  )
    (setq cr (reverse coordinate))
  )


(defun main_dialog()
  (if (not (new_dialog "draw_polyline" dcl_id)) (exit))

  (start_image "c1")(fill_image 0 0 500 500 (atoi (getvar "cecolor")))(end_image)

  (set_tile "specify_x" specify_x)
  (set_tile "specify_y" specify_y)
  (set_tile "line_width" line_width)
  (set_tile "close1" close1)
  (set_tile "sm" sm)
  
  (action_tile "col" "(done_dialog 3)")
  (action_tile "hide" "(done_dialog 4)")
  (action_tile "specify_x" "(setq specify_x $value)")
  (action_tile "specify_y" "(setq specify_y $value)")
  (action_tile "line_width" "(setq line_width $value)")
  (action_tile "sm" "(setq sm $value)")
  (action_tile "close1" "(setq close1 $value)")
  (action_tile "open_file" "(done_dialog 5)")
  (action_tile "button_Accept" "done_dialog 1")
  
  (setq w_n (start_dialog))
  (if (= w_n 3) (getcolor))
  (if (= w_n 4) (getpt))
  (if (= w_n 5) (readfile))
  (if (= w_n 1) (draw))
)
(defun C:my_lab()
	(setq w_n 2 specify_x "0" specify_y "0" line_width "bylayer" sm "1" close1 "1")
  (setq dcl_id (load_dialog "d:\\LISP\\draw_polyline.dcl"))
  (while (> w_n 0) (main_dialog))
  (unload_dialog dcl_id)
)
